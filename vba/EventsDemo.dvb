Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Public oDocEvents As AcadDocument

Private Sub oDocEvents_BeginCommand(ByVal CommandName As String)
    MsgBox "Begin" & CommandName
End Sub

Private Sub oDocEvents_EndCommand(ByVal CommandName As String)
    MsgBox "End" & CommandName
End Sub

Attribute VB_Name = "Module1"
Dim X As New Class1

Sub Main()
    Call InitializeEvents
End Sub

Sub InitializeEvents()
    Set X.oDocEvents = ThisDrawing.Application.ActiveDocument
End Sub
